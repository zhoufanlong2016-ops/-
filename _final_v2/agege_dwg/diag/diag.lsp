(defun c:TRDIAG ( / f counts ss i e d typ txt add blk)
  (setq f (open (strcat (getvar "DWGPREFIX") "diag_out.txt") "w"))
  (setq counts '())
  (defun add (k) (if (assoc k counts) (setq counts (subst (cons k (1+ (cdr (assoc k counts)))) (assoc k counts) counts)) (setq counts (cons (cons k 1) counts))))
  (defun scan (e owner / d typ txt)
    (setq d (entget e) typ (cdr (assoc 0 d)))
    (add typ)
    (cond
      ((member typ '("MTEXT" "TEXT" "ATTRIB" "ATTDEF"))
        (setq txt (cdr (assoc 1 d)))
        (if (or (vl-string-search "%%" txt) (vl-string-search "\U+" txt) (vl-string-search "\u+" txt))
          (write-line (strcat "CTRL " owner " " typ " " (substr txt 1 200)) f)))
      ((member typ '("MULTILEADER" "ACAD_TABLE" "DIMENSION" "INSERT" "ARC_TEXT" "RTEXT"))
        (if (and (= typ "MULTILEADER") (assoc 304 d)) (write-line (strcat "MLEADER " owner " " (substr (cdr (assoc 304 d)) 1 200)) f))
        (if (= typ "ACAD_TABLE") (write-line (strcat "TABLE " owner) f))
        (if (and (= typ "DIMENSION") (assoc 1 d) (/= (cdr (assoc 1 d)) "")) (write-line (strcat "DIMTXT " owner " " (cdr (assoc 1 d))) f)))
    ))
  (setq ss (ssget "_X"))
  (setq i 0)
  (if ss (repeat (sslength ss) (scan (ssname ss i) "layout") (setq i (1+ i))))
  (setq blk (tblnext "BLOCK" T))
  (while blk
    (if (and (not (wcmatch (cdr (assoc 2 blk)) "`**")) (= 0 (logand 4 (cdr (assoc 70 blk)))))
      (progn (setq e (cdr (assoc -2 blk)))
        (while e (scan e (strcat "block:" (cdr (assoc 2 blk)))) (setq e (entnext e)))))
    (if (/= 0 (logand 4 (cdr (assoc 70 blk)))) (write-line (strcat "XREF " (cdr (assoc 2 blk))) f))
    (setq blk (tblnext "BLOCK")))
  (foreach c counts (write-line (strcat "COUNT " (car c) " " (itoa (cdr c))) f))
  (close f) (princ))
